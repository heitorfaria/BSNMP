BAYOUR-COM-MIB DEFINITIONS ::= BEGIN
-- $Id: BAYOUR-COM-MIB.txt,v 1.16 2006/02/07 10:10:19 turbo Exp $

-- This is my very first MIB! A lot of it is taken from the IF-MIB
-- by the IETF Interfaces MIB Working Group (200006140000).

-- {{{ Imports
IMPORTS
  MODULE-IDENTITY, OBJECT-TYPE, Integer32, enterprises FROM SNMPv2-SMI
  MODULE-COMPLIANCE, OBJECT-GROUP                      FROM SNMPv2-CONF
  TEXTUAL-CONVENTION, DisplayString                    FROM SNMPv2-TC;
-- }}}

-- {{{ bayourCom Module identity
bayourCom MODULE-IDENTITY
  LAST-UPDATED                         "200602051008Z"  -- February 5, 2006
  ORGANIZATION                         "Bayour.COM"
  CONTACT-INFO                         "Postal:      Turbo Fredriksson
                                                     Naverlursgatan 8
                                                     421 44 Vastra Frolunda
                                                     Sweden

                                        Tel:         +46 704-697645
                                        E-Mail:      turbo@bayour.com"
  DESCRIPTION                          "The MIB module defines the Bayour.COM Bind9 and Bacula statistics."

  REVISION                             "200602051008Z"  -- February 5, 2006
  DESCRIPTION                          "* Add the packageStats information and conformance stuff.
                                        * Add some more folding tags.
                                        * Correct the folding tags informational OID numbers."

  REVISION                             "200510311440Z"  -- October 31, 2005
  DESCRIPTION                          "Change all Counter32's in baculaStats to Integer32's. I've missunderstood
                                        the meaning of Counters's!"

  REVISION                             "200510280655Z"  -- October 28, 2005
  DESCRIPTION                          "* Change all Counter32's in the b9st{Totals,Domains}Table's to Integer32's.
                                          I've missunderstood the meaning of Counters's!
                                        * Add systemStats (and corresponding systemConformance) branch where some
                                          misc system statistics will end up.
                                          This will be (for starters) uptime, memory/swap information and CPU load."

  REVISION                             "200510211259Z"  -- October 21, 2005 - 12:59
  DESCRIPTION                          "* Add a new table containing the counter names - baculaStatsCountersTable.
                                        * The CounterIndex MUST have a range - 0..2147483647 (a full Integer32)."

  REVISION                             "200510201556Z"  -- October 20, 2005 - 15:56
  DESCRIPTION                          "* Change back all Counter64 to Counter32 - can't use Counter64 in a
                                          pass-through scripts because of SMIv1 specification(s)!
                                        * Remove the JobType - missread the SQL table. It's actually a string.
                                        * Remove the baculaStatsCounter. AGAIN. It STILL fucks up the table.
                                          I just don't know why I keep adding it!!"

  REVISION                             "200510191032Z"  -- October 19, 2005 - 10:32
  DESCRIPTION                          "* Job Bytes and Pool Retention, Duration and Bytes and also the Media
                                          writes must be Counter64 because of the size of the value(s).
                                        * Tree missing columns in the Media table added: baculaMediaPool,
                                          baculaMediaType and baculaMediaLabelDate."

  REVISION                             "200510141115Z"  -- October 14, 2005 - 11:15
  DESCRIPTION                          "Missing 'baculaClientCounter' column in the 'BaculaClientsTable' added."

  REVISION                             "200510132053Z"  -- October 13, 2005 - 20:53
  DESCRIPTION                          "* Remove the 0..255 size for DisplayString - it's the default value anyway.
                                        * Rewrite the bacula{Clients,Stats}Table again. Let's see if we can get it
                                          to work this time around...
                                          - The clients table does now ONLY contain information about the client
                                          - A couple on new columns in the stats table
                                        * Add the baculaPools and baculaMedia tables (with 20 and 26 columns respectivly)
                                          with information (writable) about the pools and media library in Bacula.
                                          - Create some textual conventions that ease the setup of some of the Pools
                                            and Media table columns.
                                          - Add baculaGroupPools and baculaGroupMedia used for these two new tables.
                                          - Add two new counters for these tables - baculaTotalPools and baculaTotalMedia.
                                        * Change all entry sequences; put the word 'Entry' right after the table base
                                          instead of at the end - 'B9stEntryTotals' to 'B9stTotalsEntry' makes it
                                          follow the table name ('b9stTotalsTable'). Recomended by SMIv2."

  REVISION                             "200510120724Z"  -- October 12, 2005 - 07:24
  DESCRIPTION                          "* Add folding tags (for/in Emacs) to ease readability.
                                        * Include the TimeStamp text convention from SNMPv2-TC and change the
                                          baculaDate{Start,End} to that instead of DisplayString.
                                        * Move the conformance branch to .0 instead of .10. Might need the room
                                          above 'baculaStats' (.3).
                                        * Make sure all the indexes have access 'not-accessible' instead of
                                          'read-only' - the're indexes.
                                        * Rename the 'baculaClientsTotals' branch to 'baculaTotalClients'.
                                        * Put back 'baculaTotalTypes' and 'baculaTotalStats' which was removed
                                          at a previous commit. Need it after all.
                                        * Modify the description of the 'baculaTotalClients' slightly.
                                        * Instead of ONE table, put the Bacula statistics in two, 'linked' tables.
                                          The new table is: 'baculaStatsTable' which contain the actuall statistic
                                          counters previosly found in the 'baculaClientsTable' table. That table
                                          now only contain the client name(s) and job name(s)."

  REVISION                             "200510061645Z" -- October 6, 2005 - 16:45
  DESCRIPTION                          "Subdivide the 'conformance' branch (branch between that and
                                        'b9st{Compliance,Groups}'; same for the bacula conformance."

  REVISION                             "200510051348Z" -- October 5, 2005 - 13:48
  DESCRIPTION                          "Added the bacula statistics definitions."

  REVISION                             "200504011437Z" -- April 1, 2005 - 14:37
  DESCRIPTION                          "Changed recursive to recursion;
                                        Changed failed to failure;
                                        This according to original Bind9 definitions."

  REVISION                             "200504010000Z" -- April 1, 2005
  DESCRIPTION                          "Initial 'release'."
  ::= { enterprises 8767 }

  snmp                                 OBJECT IDENTIFIER ::= { bayourCom 2 }
-- }}}

    -- {{{ Textual conventions
    -- {{{ CounterIndex
    CounterIndex                       ::= TEXTUAL-CONVENTION
      DISPLAY-HINT                     "d"
      STATUS                           current
      DESCRIPTION                      "A unique value, greater than zero, for each type of
                                        counter in the managed system. It is recommended that
                                        values are assigned contiguously starting from 1.
                                        The value for each counter sub-layer must remain
                                        constant at least from one re-initialization of the
                                        entity's network management system to the next
                                        re-initialization."
      SYNTAX                            Integer32 (0..2147483647)
-- }}}

    -- {{{ TrueFalse
    TrueFalse                          ::= TEXTUAL-CONVENTION
      STATUS                           current
      DESCRIPTION                      "True or False values:

                                          false - 0
                                          true  - 1"
      SYNTAX                           INTEGER {
                                         false(0),
                                         true(1)
                                       }
-- }}}

    -- {{{ Status
    Status                             ::= TEXTUAL-CONVENTION
      STATUS                           current
      DESCRIPTION                      "Job status values:
                                          a - 
                                          r - 
                                          t - 
                                          f - "
      SYNTAX                           INTEGER {
                                         a(1),
                                         r(2),
                                         t(3),
                                         f(4)
                                       }
-- }}}

    -- {{{ Level
    Level                              ::= TEXTUAL-CONVENTION
      STATUS                           current
      DESCRIPTION                      "Job level values:
                                          d - 
                                          f - Full backup
                                          i - Incremental backup"
      SYNTAX                           INTEGER {
                                         d(0),
                                         f(2),
                                         i(3)
                                       }
-- }}}

    -- {{{ VolumeStatus
    VolumeStatus                       ::= TEXTUAL-CONVENTION
      STATUS                           current
      DESCRIPTION                      "Volume status values:
                                          Full        - 
                                          Archive     - 
                                          Append      - 
                                          Recycle     - 
                                          Purged      - 
                                          Read-Only   - 
                                          Disabled    - 
                                          Error       - 
                                          Busy        - 
                                          Used        - 
                                          Cleaning    - "
      SYNTAX                           INTEGER {
                                         full(1),
                                         archive(2),
                                         append(3),
                                         recycle(4),
                                         purged(5),
                                         readonly(6),
                                         disabled(7),
                                         error(8),
                                         busy(9),
                                         used(10),
                                         cleaning(11)
                                       }
-- }}}
-- }}}

    -- {{{ .1.3.6.1.4.1.8767.2.0 conformance
    conformance                        OBJECT IDENTIFIER ::= { snmp 0 }
      -- {{{ .1.3.6.1.4.1.8767.2.0.1 bind9Conformance
      bind9Conformance                 OBJECT IDENTIFIER ::= { conformance 1 }
        -- {{{ .1.3.6.1.4.1.8767.2.0.1.1 b9stCompliance
        b9stCompliance                 MODULE-COMPLIANCE
          STATUS                       current
          DESCRIPTION                  "The compliance statement for SNMP entities which have
                                        bind9 status counters."
          MODULE  -- this module
          MANDATORY-GROUPS             { b9stGroupTotals, b9stGroupDomains }
          ::= { bind9Conformance 1 }
-- }}}

        -- {{{ .1.3.6.1.4.1.8767.2.0.1.2 b9stGroups
        b9stGroups                     OBJECT IDENTIFIER ::= { bind9Conformance 2 }
          b9stGroupTotals              OBJECT-GROUP
            OBJECTS                    { b9stNumberTotals, b9stCounterName, b9stCounterTotal,
                                         b9stCounterForward, b9stCounterReverse }
            STATUS                     current
            DESCRIPTION                "A collection of objects providing information
                                        applicable to B9st statistics."
            ::= { b9stGroups 1 }

          b9stGroupDomains             OBJECT-GROUP
            OBJECTS                    { b9stNumberDomains, b9stDomainName, b9stCounterSuccess,
                                         b9stCounterReferral, b9stCounterNXRRSet, b9stCounterNXDomain,
                                         b9stCounterRecursion, b9stCounterFailure }
            STATUS                     current
            DESCRIPTION                "A collection of objects providing information
                                        applicable to B9st statistics."
            ::= { b9stGroups 2 }
-- }}}
-- }}}

      -- {{{ .1.3.6.1.4.1.8767.2.0.2 baculaConformance
      baculaConformance                OBJECT IDENTIFIER ::= { conformance 2 }
        -- {{{ .1.3.6.1.4.1.8767.2.0.2.1 baculaCompliance
        baculaCompliance               MODULE-COMPLIANCE
          STATUS                       current
          DESCRIPTION                  "The compliance statement for SNMP entities which have
                                        bacula status counters."
          MODULE                       -- this module
          MANDATORY-GROUPS             { baculaGroupClients, baculaGroupJobNames, baculaGroupJobIDs,
                                         baculaGroupCounters, baculaGroupStats, baculaGroupPools,
                                         baculaGroupMedia }
          ::= { baculaConformance 1 }
-- }}}

        -- {{{ .1.3.6.1.4.1.8767.2.0.2.2 baculaGroups
        baculaGroups                   OBJECT IDENTIFIER ::= { baculaConformance 2 }
          baculaGroupClients           OBJECT-GROUP
            OBJECTS                    { baculaTotalClients, baculaClientName, baculaClientUname,
                                         baculaClientAutoPrune, baculaClientRetentionFile,
                                         baculaClientRetentionJob }
            STATUS                     current
            DESCRIPTION                "A collection of objects providing information
                                        applicable to Bacula statistics."
            ::= { baculaGroups 1 }

          baculaGroupJobNames          OBJECT-GROUP
            OBJECTS                    { baculaJobsName, baculaJobsDesc, baculaJobsMD5, baculaJobsCreate }
            STATUS                     current
            DESCRIPTION                "A collection of objects providing information
                                        applicable to Bacula statistics."
            ::= { baculaGroups 2 }

          baculaGroupJobIDs            OBJECT-GROUP
            OBJECTS                    { baculaJobsID }
            STATUS                     current
            DESCRIPTION                "A collection of objects providing information
                                        applicable to Bacula statistics."
            ::= { baculaGroups 3 }

          baculaGroupCounters          OBJECT-GROUP
            OBJECTS                    { baculaStatsCounterName }
            STATUS                     current
            DESCRIPTION                "A collection of objects providing information
                                        applicable to Bacula statistics."
            ::= { baculaGroups 4 }


          baculaGroupStats             OBJECT-GROUP
            OBJECTS                    { baculaTotalStats, baculaStatsStart, baculaStatsEnd,
                                         baculaStatsDuration, baculaStatsFiles, baculaStatsBytes,
                                         baculaStatsType, baculaStatsStatus, baculaStatsLevel,
                                         baculaStatsErrors, baculaStatsMissingFiles }
            STATUS                     current
            DESCRIPTION                "A collection of objects providing information
                                        applicable to Bacula statistics."
            ::= { baculaGroups 5 }

          baculaGroupPools             OBJECT-GROUP
            OBJECTS                    { baculaTotalPools, baculaPoolsName, baculaPoolsNum,
                                         baculaPoolsMax, baculaPoolsUseOnce, baculaPoolsUseCatalog,
                                         baculaPoolsAcceptAnyVolume, baculaPoolsRetention,
                                         baculaPoolsDuration, baculaPoolsMaxJobs, baculaPoolsMaxFiles,
                                         baculaPoolsMaxBytes, baculaPoolsAutoPrune, baculaPoolsRecycle,
                                         baculaPoolsType, baculaPoolsLabelFormat, baculaPoolsEnabled,
                                         baculaPoolsScratchPoolID, baculaPoolsRecyclePoolID }
            STATUS                     current
            DESCRIPTION                "A collection of objects providing information
                                        applicable to Bacula statistics."
            ::= { baculaGroups 6 }

          baculaGroupMedia             OBJECT-GROUP
            OBJECTS                    { baculaTotalMedia, baculaMediaName, baculaMediaSlot,
                                         baculaMediaPool, baculaMediaType, baculaMediaWrittenFirst,
                                         baculaMediaWrittenLast, baculaMediaLabelDate, baculaMediaJobs,
                                         baculaMediaFiles, baculaMediaBlocks, baculaMediaMounts,
                                         baculaMediaBytes, baculaMediaErrors, baculaMediaWrites,
                                         baculaMediaCapacity, baculaMediaStatus, baculaMediaRecycle,
                                         baculaMediaRetention, baculaMediaDuration, baculaMediaMaxJobs,
                                         baculaMediaMaxFiles, baculaMediaMaxBytes, baculaMediaInChanger,
                                         baculaMediaMediaAddressing, baculaMediaReadTime, baculaMediaWriteTime,
                                         baculaMediaEndFile, baculaMediaEndBlock }
            STATUS                     current
            DESCRIPTION                "A collection of objects providing information
                                        applicable to Bacula statistics."
            ::= { baculaGroups 7 }
-- }}}
-- }}}

      -- {{{ .1.3.6.1.4.1.8767.2.0.3 systemConformance
      systemConformance                OBJECT IDENTIFIER ::= { conformance 3 }
        -- {{{ .1.3.6.1.4.1.8767.2.0.3.1 systemCompliance
        systemCompliance               MODULE-COMPLIANCE
          STATUS                       current
          DESCRIPTION                  "The compliance statement for SNMP entities which have
                                        system status counters."
          MODULE                       -- this module
          MANDATORY-GROUPS             { systemGroupMemory, systemGroupCPU, systemGroupLoad,
                                         systemGroupMisc }
          ::= { systemConformance 1 }
-- }}}

        -- {{{ .1.3.6.1.4.1.8767.2.0.3.2 systemgroups
        systemGroups                   OBJECT IDENTIFIER ::= { systemConformance 2 }
          systemGroupMemory            OBJECT-GROUP
            OBJECTS                    { systemMemoryTotal, systemMemoryUsed, systemMemoryBuffered,
                                         systemMemoryCached, systemMemorySwapTotal, systemMemorySwapUsed }
            STATUS                     current
            DESCRIPTION                "A collection of objects providing information
                                        applicable to System memory statistics."
            ::= { systemGroups 1 }

          systemGroupCPU               OBJECT-GROUP
            OBJECTS                    { systemCPUTasksTotal, systemCPUTasksRunning, systemCPUTasksSleeping,
                                         systemCPUTasksStopped, systemCPUTasksZombies, systemCPUUsageUser,
                                         systemCPUUsageSystem, systemCPUUsageNice, systemCPUUsageIdle,
                                         systemCPUUsageIOWait }
            STATUS                     current
            DESCRIPTION                "A collection of objects providing information
                                        applicable to System CPU statistics."
            ::= { systemGroups 2 }

          systemGroupLoad              OBJECT-GROUP
            OBJECTS                    { systemLoadLastOne, systemLoadLastFive, systemLoadLastFifteen }
            STATUS                     current
            DESCRIPTION                "A collection of objects providing information
                                        applicable to System load statistics."
            ::= { systemGroups 3 }

          systemGroupMisc              OBJECT-GROUP
            OBJECTS                    { systemUptime }
            STATUS                     current
            DESCRIPTION                "A collection of objects providing information
                                        applicable to misc system statistics."
            ::= { systemGroups 4 }
-- }}}
-- }}}

      -- {{{ .1.3.6.1.4.1.8767.2.0.4 packageConformance
      packageConformance               OBJECT IDENTIFIER ::= { conformance 4 }
        -- {{{ .1.3.6.1.4.1.8767.2.0.4.1 packageCompliance
        packageCompliance              MODULE-COMPLIANCE
          STATUS                       current
          DESCRIPTION                  "The compliance statement for SNMP entities which have
                                        package status information."
          MODULE                       -- this module
          MANDATORY-GROUPS             {  packageStatsGroup, packageInfoGroup }
          ::= { packageConformance 1 }
-- }}}

        -- {{{ .1.3.6.1.4.1.8767.2.0.4.2 packageGroups
        packageGroups                  OBJECT IDENTIFIER ::= { packageConformance 2 }
          packageStatsGroup            OBJECT-GROUP
            OBJECTS                    { packageName, packageVersion, packageDesc, packageStatus }
            STATUS                     current
            DESCRIPTION                "A collection of objects providing information
                                        applicable to Package statistics."
            ::= { packageGroups 1 }

          packageInfoGroup             OBJECT-GROUP
            OBJECTS                    { packagePriority, packageSection, packageMaintainer,
                                         packageSource, packageDepends, packageRecommends,
                                         packageSuggests, packageSize, packageMD5Sum }
            STATUS                     current
            DESCRIPTION                "A collection of objects providing information
                                        applicable to Package information."
            ::= { packageGroups 2 }
-- }}}
-- }}}
-- }}}

    -- {{{ .1.3.6.1.4.1.8767.2.1 bind9Stats
    bind9Stats                         OBJECT IDENTIFIER ::= { snmp 1 }
      -- {{{ .1.3.6.1.4.1.8767.2.1.x b9stNumber{Totals,Domains}
      b9stNumberTotals                 OBJECT-TYPE
        SYNTAX                         Integer32
        MAX-ACCESS                     read-only
        STATUS                         current
        DESCRIPTION                    "Number of Bind9 status counters"
        ::= { bind9Stats 1 }
  
      b9stNumberDomains                OBJECT-TYPE
        SYNTAX                         Integer32
        MAX-ACCESS                     read-only
        STATUS                         current
        DESCRIPTION                    "Number of Bind9 status counters"
        ::= { bind9Stats 2 }
-- }}}
  
      -- {{{ .1.3.6.1.4.1.8767.2.1.3 b9stTotalsTable
      b9stTotalsTable                  OBJECT-TYPE
        SYNTAX                         SEQUENCE OF B9stTotalsEntry
        MAX-ACCESS                     not-accessible
        STATUS                         current
        DESCRIPTION                    "A list of Bind9 statistic counters (totals)."
        ::= { bind9Stats 3 }
  
        b9stTotalsEntry                OBJECT-TYPE
          SYNTAX                       B9stTotalsEntry
          MAX-ACCESS                   not-accessible
          STATUS                       current
          DESCRIPTION                  "An entry containing Bind9 statistics (totals)."
          INDEX                        { b9stIndexTotals }
          ::= { b9stTotalsTable 1 }
  
          B9stTotalsEntry              ::= SEQUENCE {
            b9stIndexTotals            CounterIndex,

            b9stCounterName            DisplayString,
            b9stCounterTotal           Integer32,
            b9stCounterForward         Integer32,
            b9stCounterReverse         Integer32
          }
  
          b9stIndexTotals              OBJECT-TYPE
            SYNTAX                     CounterIndex
            MAX-ACCESS                 not-accessible
            STATUS                     current
            DESCRIPTION                "Reference Index for each counter."
            ::= { b9stTotalsEntry 1 }
  
          b9stCounterName              OBJECT-TYPE
            SYNTAX                     DisplayString
            MAX-ACCESS                 read-only
            STATUS                     current
            DESCRIPTION                "A textual string containing information about the
                                        statistics counters. This string should include the
                                        name of the counter."
            ::= { b9stTotalsEntry 2 }

          b9stCounterTotal             OBJECT-TYPE
            SYNTAX                     Integer32
            MAX-ACCESS                 read-only
            STATUS                     current
            DESCRIPTION                "Total number of request."
            ::= { b9stTotalsEntry 3 }

          b9stCounterForward           OBJECT-TYPE
            SYNTAX                     Integer32
            MAX-ACCESS                 read-only
            STATUS                     current
            DESCRIPTION                "Total number of forward requests."
            ::= { b9stTotalsEntry 4 }

          b9stCounterReverse           OBJECT-TYPE
            SYNTAX                     Integer32
            MAX-ACCESS                 read-only
            STATUS                     current
            DESCRIPTION                "Total number of reverse requests."
            ::= { b9stTotalsEntry 5 }
-- }}}

      -- {{{ .1.3.6.1.4.1.8767.2.1.4 b9stDomainsTable
      b9stDomainsTable                 OBJECT-TYPE
        SYNTAX                         SEQUENCE OF B9stDomainsEntry
        MAX-ACCESS                     not-accessible
        STATUS                         current
        DESCRIPTION                    "A list of Bind9 statistic counters"
        ::= { bind9Stats 4 }
  
        b9stDomainsEntry               OBJECT-TYPE
          SYNTAX                       B9stDomainsEntry
          MAX-ACCESS                   not-accessible
          STATUS                       current
          DESCRIPTION                  "An entry containing Bind9 statistics"
          INDEX                        { b9stIndexDomains }
          ::= { b9stDomainsTable 1 }
  
          B9stDomainsEntry             ::= SEQUENCE {
            b9stIndexDomains           CounterIndex,

            b9stDomainName             DisplayString,
            b9stCounterSuccess         Integer32,
            b9stCounterReferral        Integer32,
            b9stCounterNXRRSet         Integer32,
            b9stCounterNXDomain        Integer32,
            b9stCounterRecursion       Integer32,
            b9stCounterFailure         Integer32
          }
  
          b9stIndexDomains             OBJECT-TYPE
            SYNTAX                     CounterIndex
            MAX-ACCESS                 not-accessible
            STATUS                     current
            DESCRIPTION                "Reference Index for each counter."
            ::= { b9stDomainsEntry 1 }
  
          b9stDomainName               OBJECT-TYPE
            SYNTAX                     DisplayString
            MAX-ACCESS                 read-only
            STATUS                     current
            DESCRIPTION                "A textual string containing information about the
                                        statistics counters. This string should include the
                                        name of the counter."
            ::= { b9stDomainsEntry 2 }

          b9stCounterSuccess           OBJECT-TYPE
            SYNTAX                     Integer32
            MAX-ACCESS                 read-only
            STATUS                     current
            DESCRIPTION                "Total number of reverse requests."
            ::= { b9stDomainsEntry 3 }

          b9stCounterReferral          OBJECT-TYPE
            SYNTAX                     Integer32
            MAX-ACCESS                 read-only
            STATUS                     current
            DESCRIPTION                "Total number of reverse requests."
            ::= { b9stDomainsEntry 4 }

          b9stCounterNXRRSet           OBJECT-TYPE
            SYNTAX                     Integer32
            MAX-ACCESS                 read-only
            STATUS                     current
            DESCRIPTION                "Total number of reverse requests."
            ::= { b9stDomainsEntry 5 }

          b9stCounterNXDomain          OBJECT-TYPE
            SYNTAX                     Integer32
            MAX-ACCESS                 read-only
            STATUS                     current
            DESCRIPTION                "Total number of reverse requests."
            ::= { b9stDomainsEntry 6 }

          b9stCounterRecursion         OBJECT-TYPE
            SYNTAX                     Integer32
            MAX-ACCESS                 read-only
            STATUS                     current
            DESCRIPTION                "Total number of reverse requests."
            ::= { b9stDomainsEntry 7 }

          b9stCounterFailure           OBJECT-TYPE
            SYNTAX                     Integer32
            MAX-ACCESS                 read-only
            STATUS                     current
            DESCRIPTION                "Total number of reverse requests."
            ::= { b9stDomainsEntry 8 }
-- }}}
-- }}}

    -- {{{ .1.3.6.1.4.1.8767.2.2 qmailStats
    qmailStats                         OBJECT IDENTIFIER ::= { snmp 2 }
-- }}}

    -- {{{ .1.3.6.1.4.1.8767.2.3 baculaStats
    baculaStats                        OBJECT IDENTIFIER ::= { snmp 3 }
      -- {{{ .1.3.6.1.4.1.8767.2.3.x  baculaTotal{Clients,Stats,Pools,Media}
      baculaTotalClients               OBJECT-TYPE
        SYNTAX                         Integer32
        MAX-ACCESS                     read-only
        STATUS                         current
        DESCRIPTION                    "Total number of Bacula clients."
        ::= { baculaStats 1 }

      baculaTotalStats                 OBJECT-TYPE
        SYNTAX                         Integer32
        MAX-ACCESS                     read-only
        STATUS                         current
        DESCRIPTION                    "Total number of Bacula statistics."
        ::= { baculaStats 2 }

      baculaTotalPools                 OBJECT-TYPE
        SYNTAX                         Integer32
        MAX-ACCESS                     read-only
        STATUS                         current
        DESCRIPTION                    "Total number of Bacula pool entries."
        ::= { baculaStats 3 }

      baculaTotalMedia                 OBJECT-TYPE
        SYNTAX                         Integer32
        MAX-ACCESS                     read-only
        STATUS                         current
        DESCRIPTION                    "Total number of Bacula media entries."
        ::= { baculaStats 4 }
-- }}}

      -- {{{ .1.3.6.1.4.1.8767.2.3.5  baculaClientsTable
      baculaClientsTable               OBJECT-TYPE
        SYNTAX                         SEQUENCE OF BaculaClientsEntry
        MAX-ACCESS                     not-accessible
        STATUS                         current
        DESCRIPTION                    "A list of bacula statistic counters"
        ::= { baculaStats 5 }
  
        baculaClientsEntry             OBJECT-TYPE
          SYNTAX                       BaculaClientsEntry
          MAX-ACCESS                   not-accessible
          STATUS                       current
          DESCRIPTION                  "An entry containing bacula statistics"
          INDEX                        { baculaClientsIndex }
          ::= { baculaClientsTable 1 }
  
          BaculaClientsEntry           ::= SEQUENCE {
            baculaClientsIndex         CounterIndex,

            baculaClientName           DisplayString,
            baculaClientUname          DisplayString,
            baculaClientAutoPrune      TrueFalse,
            baculaClientRetentionFile  Integer32,
            baculaClientRetentionJob   Integer32
          }
  
          baculaClientsIndex           OBJECT-TYPE
            SYNTAX                     CounterIndex
            MAX-ACCESS                 not-accessible
            STATUS                     current
            DESCRIPTION                "Reference Index for each counter."
            ::= { baculaClientsEntry 1 }
  
          baculaClientName             OBJECT-TYPE
            SYNTAX                     DisplayString
            MAX-ACCESS                 read-only
            STATUS                     current
            DESCRIPTION                "A textual string containing information about the
                                        statistics counters. This string should include the
                                        name of the counter."
            ::= { baculaClientsEntry 2 }

          baculaClientUname            OBJECT-TYPE
            SYNTAX                     DisplayString
            MAX-ACCESS                 read-only
            STATUS                     current
            DESCRIPTION                "A textual string containing information about the job."
            ::= { baculaClientsEntry 3 }

          baculaClientAutoPrune        OBJECT-TYPE
            SYNTAX                     TrueFalse
            MAX-ACCESS                 read-write
            STATUS                     current
            DESCRIPTION                "A textual string containing information about the job."
            ::= { baculaClientsEntry 4 }

          baculaClientRetentionFile    OBJECT-TYPE
            SYNTAX                     Integer32
            MAX-ACCESS                 read-write
            STATUS                     current
            DESCRIPTION                "A textual string containing information about the job."
            ::= { baculaClientsEntry 5 }

          baculaClientRetentionJob     OBJECT-TYPE
            SYNTAX                     Integer32
            MAX-ACCESS                 read-write
            STATUS                     current
            DESCRIPTION                "A textual string containing information about the job."
            ::= { baculaClientsEntry 6 }

-- }}}

      -- {{{ .1.3.6.1.4.1.8767.2.3.6  baculaJobsNameTable
      baculaJobsNameTable              OBJECT-TYPE
        SYNTAX                         SEQUENCE OF BaculaJobsNameEntry
        MAX-ACCESS                     not-accessible
        STATUS                         current
        DESCRIPTION                    "A list of bacula statistic counters"
        ::= { baculaStats 6 }
  
        baculaJobsNameEntry            OBJECT-TYPE
          SYNTAX                       BaculaJobsNameEntry
          MAX-ACCESS                   not-accessible
          STATUS                       current
          DESCRIPTION                  "An entry containing bacula statistics"
          INDEX                        { baculaClientsIndex, baculaJobsNameIndex }
          ::= { baculaJobsNameTable 1 }
  
          BaculaJobsNameEntry          ::= SEQUENCE {
            baculaJobsNameIndex        CounterIndex,

            baculaJobsName             DisplayString,
            baculaJobsDesc             DisplayString,
            baculaJobsMD5              DisplayString,
            baculaJobsCreate           DisplayString
          }
  
          baculaJobsNameIndex          OBJECT-TYPE
            SYNTAX                     CounterIndex
            MAX-ACCESS                 not-accessible
            STATUS                     current
            DESCRIPTION                "Reference Index for each counter."
            ::= { baculaJobsNameEntry 1 }
  
          baculaJobsName               OBJECT-TYPE
            SYNTAX                     DisplayString
            MAX-ACCESS                 read-only
            STATUS                     current
            DESCRIPTION                "A textual string containing the NAME of the job."
            ::= { baculaJobsNameEntry 2 }

          baculaJobsDesc               OBJECT-TYPE
            SYNTAX                     DisplayString
            MAX-ACCESS                 read-only
            STATUS                     current
            DESCRIPTION                "A textual string containing the DESCRIPTION of the job."
            ::= { baculaJobsNameEntry 3 }

          baculaJobsMD5                OBJECT-TYPE
            SYNTAX                     DisplayString
            MAX-ACCESS                 read-only
            STATUS                     current
            DESCRIPTION                "A textual string containing the MD5 sum of the job."
            ::= { baculaJobsNameEntry 4 }

          baculaJobsCreate             OBJECT-TYPE
            SYNTAX                     DisplayString
            MAX-ACCESS                 read-only
            STATUS                     current
            DESCRIPTION                "A textual string containing the create time of the job."
            ::= { baculaJobsNameEntry 5 }
-- }}}

      -- {{{ .1.3.6.1.4.1.8767.2.3.7  baculaJobsIDTable
      baculaJobsIDTable                OBJECT-TYPE
        SYNTAX                         SEQUENCE OF BaculaJobsIDEntry
        MAX-ACCESS                     not-accessible
        STATUS                         current
        DESCRIPTION                    "A list of bacula statistic counters"
        ::= { baculaStats 7 }
  
        baculaJobsIDEntry              OBJECT-TYPE
          SYNTAX                       BaculaJobsIDEntry
          MAX-ACCESS                   not-accessible
          STATUS                       current
          DESCRIPTION                  "An entry containing bacula statistics"
          INDEX                        { baculaClientsIndex, baculaJobsNameIndex, baculaJobsIDIndex }
          ::= { baculaJobsIDTable 1 }
  
          BaculaJobsIDEntry            ::= SEQUENCE {
            baculaJobsIDIndex          CounterIndex,

            baculaJobsID               DisplayString
          }
  
          baculaJobsIDIndex            OBJECT-TYPE
            SYNTAX                     CounterIndex
            MAX-ACCESS                 not-accessible
            STATUS                     current
            DESCRIPTION                "Reference Index for each counter."
            ::= { baculaJobsIDEntry 1 }
  
          baculaJobsID                 OBJECT-TYPE
            SYNTAX                     DisplayString
            MAX-ACCESS                 read-only
            STATUS                     current
            DESCRIPTION                "A textual string containing the ID of the job."
            ::= { baculaJobsIDEntry 2 }
-- }}}

      -- {{{ .1.3.6.1.4.1.8767.2.3.8  baculaStatsCountersTable
      baculaStatsCountersTable        OBJECT-TYPE
        SYNTAX                        SEQUENCE OF BaculaStatsCountersEntry
        MAX-ACCESS                    not-accessible
        STATUS                        current
        DESCRIPTION                   "A list of bacula statistic counter names."
        ::= { baculaStats 8 }

        baculaStatsCountersEntry        OBJECT-TYPE
          SYNTAX                        BaculaStatsCountersEntry
          MAX-ACCESS                    not-accessible
          STATUS                        current
          DESCRIPTION                   "An entry containing bacula statistic counter names."
          INDEX                         { baculaStatsCountersIndex }
          ::= { baculaStatsCountersTable 1 }

          BaculaStatsCountersEntry      ::= SEQUENCE {
            baculaStatsCountersIndex    CounterIndex,

            baculaStatsCounterName      DisplayString
          }

          baculaStatsCountersIndex      OBJECT-TYPE
            SYNTAX                      CounterIndex
            MAX-ACCESS                  not-accessible
            STATUS                      current
            DESCRIPTION                 "Reference Index for each counter name."
            ::= { baculaStatsCountersEntry 1 }

          baculaStatsCounterName        OBJECT-TYPE
            SYNTAX                      DisplayString
            MAX-ACCESS                  read-only
            STATUS                      current
            DESCRIPTION                 "Names of the counter values."
            ::= { baculaStatsCountersEntry 2 }
-- }}}

      -- {{{ .1.3.6.1.4.1.8767.2.3.9  baculaStatsTable
      baculaStatsTable                 OBJECT-TYPE
        SYNTAX                         SEQUENCE OF BaculaStatsEntry
        MAX-ACCESS                     not-accessible
        STATUS                         current
        DESCRIPTION                    "A list of bacula statistic counters"
        ::= { baculaStats 9 }
  
        baculaStatsEntry               OBJECT-TYPE
          SYNTAX                       BaculaStatsEntry
          MAX-ACCESS                   not-accessible
          STATUS                       current
          DESCRIPTION                  "An entry containing bacula statistics"
          INDEX                        { baculaClientsIndex, baculaJobsNameIndex, baculaJobsIDIndex, baculaStatsIndex }
          ::= { baculaStatsTable 1 }
  
          BaculaStatsEntry             ::= SEQUENCE {
            baculaStatsIndex           CounterIndex,

            baculaStatsStart           DisplayString,
            baculaStatsEnd             DisplayString,
            baculaStatsDuration        Integer32,
            baculaStatsFiles           Integer32,
            baculaStatsBytes           Integer32,
            baculaStatsType            DisplayString,
            baculaStatsStatus          Status,
            baculaStatsLevel           Level,
            baculaStatsErrors          Integer32,
            baculaStatsMissingFiles    Integer32
          }
  
          baculaStatsIndex             OBJECT-TYPE
            SYNTAX                     CounterIndex
            MAX-ACCESS                 not-accessible
            STATUS                     current
            DESCRIPTION                "Reference Index for each counter."
            ::= { baculaStatsEntry 1 }
  
          baculaStatsStart             OBJECT-TYPE
            SYNTAX                     DisplayString
            MAX-ACCESS                 read-only
            STATUS                     current
            DESCRIPTION                "Date and time of job start."
            ::= { baculaStatsEntry 2 }

          baculaStatsEnd               OBJECT-TYPE
            SYNTAX                     DisplayString
            MAX-ACCESS                 read-only
            STATUS                     current
            DESCRIPTION                "Date and time of job completion."
            ::= { baculaStatsEntry 3 }

          baculaStatsDuration          OBJECT-TYPE
            SYNTAX                     Integer32
            MAX-ACCESS                 read-only
            STATUS                     current
            DESCRIPTION                "Duration of job."
            ::= { baculaStatsEntry 4 }

          baculaStatsFiles             OBJECT-TYPE
            SYNTAX                     Integer32 (1..2147483647)
            MAX-ACCESS                 read-only
            STATUS                     current
            DESCRIPTION                "Files backed up in the job."
            ::= { baculaStatsEntry 5 }

          baculaStatsBytes             OBJECT-TYPE
            SYNTAX                     Integer32
            MAX-ACCESS                 read-only
            STATUS                     current
            DESCRIPTION                "Bytes backed up in the job."
            ::= { baculaStatsEntry 6 }

          baculaStatsType              OBJECT-TYPE
            SYNTAX                     DisplayString
            MAX-ACCESS                 read-only
            STATUS                     current
            DESCRIPTION                "Files backed up in the job."
            ::= { baculaStatsEntry 7 }

          baculaStatsStatus            OBJECT-TYPE
            SYNTAX                     Status
            MAX-ACCESS                 read-only
            STATUS                     current
            DESCRIPTION                "Files backed up in the job."
            ::= { baculaStatsEntry 8 }

          baculaStatsLevel             OBJECT-TYPE
            SYNTAX                     Level
            MAX-ACCESS                 read-only
            STATUS                     current
            DESCRIPTION                "Files backed up in the job."
            ::= { baculaStatsEntry 9 }

          baculaStatsErrors            OBJECT-TYPE
            SYNTAX                     Integer32 (1..2147483647)
            MAX-ACCESS                 read-only
            STATUS                     current
            DESCRIPTION                "Files backed up in the job."
            ::= { baculaStatsEntry 10 }

          baculaStatsMissingFiles      OBJECT-TYPE
            SYNTAX                     Integer32 (1..2147483647)
            MAX-ACCESS                 read-only
            STATUS                     current
            DESCRIPTION                "Files backed up in the job."
            ::= { baculaStatsEntry 11 }

-- }}}

      -- {{{ .1.3.6.1.4.1.8767.2.3.10 baculaPoolsTable
      baculaPoolsTable                 OBJECT-TYPE
        SYNTAX                         SEQUENCE OF BaculaPoolsEntry
        MAX-ACCESS                     not-accessible
        STATUS                         current
        DESCRIPTION                    "A list of bacula pool information."
        ::= { baculaStats 10 }
  
        baculaPoolsEntry               OBJECT-TYPE
          SYNTAX                       BaculaPoolsEntry
          MAX-ACCESS                   not-accessible
          STATUS                       current
          DESCRIPTION                  "An entry containing bacula statistics"
          INDEX                        { baculaPoolsIndex }
          ::= { baculaPoolsTable 1 }
  
          BaculaPoolsEntry             ::= SEQUENCE {
            baculaPoolsIndex           CounterIndex,

            baculaPoolsName            DisplayString,
            baculaPoolsNum             Integer32,
            baculaPoolsMax             Integer32,
            baculaPoolsUseOnce         TrueFalse,
            baculaPoolsUseCatalog      TrueFalse,
            baculaPoolsAcceptAnyVolume TrueFalse,
            baculaPoolsRetention       Integer32,
            baculaPoolsDuration        Integer32,
            baculaPoolsMaxJobs         Integer32,
            baculaPoolsMaxFiles        Integer32,
            baculaPoolsMaxBytes        Integer32,
            baculaPoolsAutoPrune       TrueFalse,
            baculaPoolsRecycle         TrueFalse,
            baculaPoolsType            DisplayString,
            baculaPoolsLabelFormat     DisplayString,
            baculaPoolsEnabled         TrueFalse,
            baculaPoolsScratchPoolID   Integer32,
            baculaPoolsRecyclePoolID   Integer32
          }
  
          baculaPoolsIndex             OBJECT-TYPE
            SYNTAX                     CounterIndex
            MAX-ACCESS                 not-accessible
            STATUS                     current
            DESCRIPTION                "Reference Index for each counter."
            ::= { baculaPoolsEntry 1 }
  
          baculaPoolsName              OBJECT-TYPE
            SYNTAX                     DisplayString
            MAX-ACCESS                 read-only
            STATUS                     current
            DESCRIPTION                "Name of Bacula pool."
            ::= { baculaPoolsEntry 2 }

          baculaPoolsNum               OBJECT-TYPE
            SYNTAX                     Integer32
            MAX-ACCESS                 read-only
            STATUS                     current
            DESCRIPTION                "Number of volumes in pool."
            ::= { baculaPoolsEntry 3 }

          baculaPoolsMax               OBJECT-TYPE
            SYNTAX                     Integer32
            MAX-ACCESS                 read-only
            STATUS                     current
            DESCRIPTION                "Maximum number of volumes in pool."
            ::= { baculaPoolsEntry 4 }

          baculaPoolsUseOnce           OBJECT-TYPE
            SYNTAX                     TrueFalse
            MAX-ACCESS                 read-write
            STATUS                     current
            DESCRIPTION                "Use pool only once."
            ::= { baculaPoolsEntry 5 }

          baculaPoolsUseCatalog        OBJECT-TYPE
            SYNTAX                     TrueFalse
            MAX-ACCESS                 read-write
            STATUS                     current
            DESCRIPTION                "Use catalog."
            ::= { baculaPoolsEntry 6 }

          baculaPoolsAcceptAnyVolume   OBJECT-TYPE
            SYNTAX                     TrueFalse
            MAX-ACCESS                 read-write
            STATUS                     current
            DESCRIPTION                "Accept any volume into pool."
            ::= { baculaPoolsEntry 7 }

          baculaPoolsRetention         OBJECT-TYPE
            SYNTAX                     Integer32
            MAX-ACCESS                 read-write
            STATUS                     current
            DESCRIPTION                "Pool retention period (sec)."
            ::= { baculaPoolsEntry 8 }

          baculaPoolsDuration          OBJECT-TYPE
            SYNTAX                     Integer32
            MAX-ACCESS                 read-write
            STATUS                     current
            DESCRIPTION                "Pool duration period (sec)."
            ::= { baculaPoolsEntry 9 }

          baculaPoolsMaxJobs           OBJECT-TYPE
            SYNTAX                     Integer32 (0..10)
            MAX-ACCESS                 read-write
            STATUS                     current
            DESCRIPTION                "Maximum jobs that can use pool."
            ::= { baculaPoolsEntry 10 }

          baculaPoolsMaxFiles          OBJECT-TYPE
            SYNTAX                     Integer32 (0..10)
            MAX-ACCESS                 read-write
            STATUS                     current
            DESCRIPTION                "Maximum files in pool."
            ::= { baculaPoolsEntry 11 }

          baculaPoolsMaxBytes          OBJECT-TYPE
            SYNTAX                     Integer32
            MAX-ACCESS                 read-write
            STATUS                     current
            DESCRIPTION                "Maximum bytes in pool."
            ::= { baculaPoolsEntry 12 }

          baculaPoolsAutoPrune         OBJECT-TYPE
            SYNTAX                     TrueFalse
            MAX-ACCESS                 read-write
            STATUS                     current
            DESCRIPTION                "Auto prune volumes in pool."
            ::= { baculaPoolsEntry 13 }

          baculaPoolsRecycle           OBJECT-TYPE
            SYNTAX                     TrueFalse
            MAX-ACCESS                 read-write
            STATUS                     current
            DESCRIPTION                "Recycle volumes in pool."
            ::= { baculaPoolsEntry 14 }

          baculaPoolsType              OBJECT-TYPE
            SYNTAX                     DisplayString
            MAX-ACCESS                 read-write
            STATUS                     current
            DESCRIPTION                "Type of pool."
            ::= { baculaPoolsEntry 15 }

          baculaPoolsLabelFormat       OBJECT-TYPE
            SYNTAX                     DisplayString
            MAX-ACCESS                 read-write
            STATUS                     current
            DESCRIPTION                "Pool label format."
            ::= { baculaPoolsEntry 16 }

          baculaPoolsEnabled           OBJECT-TYPE
            SYNTAX                     TrueFalse
            MAX-ACCESS                 read-write
            STATUS                     current
            DESCRIPTION                "Enable pool."
            ::= { baculaPoolsEntry 17 }

          baculaPoolsScratchPoolID     OBJECT-TYPE
            SYNTAX                     Integer32
            MAX-ACCESS                 read-only
            STATUS                     current
            DESCRIPTION                "Scratch pool ID."
            ::= { baculaPoolsEntry 18 }

          baculaPoolsRecyclePoolID     OBJECT-TYPE
            SYNTAX                     Integer32
            MAX-ACCESS                 read-only
            STATUS                     current
            DESCRIPTION                "Recycle pool ID."
            ::= { baculaPoolsEntry 19 }
-- }}}

      -- {{{ .1.3.6.1.4.1.8767.2.3.11 baculaMediaTable
      baculaMediaTable                 OBJECT-TYPE
        SYNTAX                         SEQUENCE OF BaculaMediaEntry
        MAX-ACCESS                     not-accessible
        STATUS                         current
        DESCRIPTION                    "A list of bacula media information."
        ::= { baculaStats 11 }
  
        baculaMediaEntry               OBJECT-TYPE
          SYNTAX                       BaculaMediaEntry
          MAX-ACCESS                   not-accessible
          STATUS                       current
          DESCRIPTION                  "An entry containing bacula statistics"
          INDEX                        { baculaMediaIndex }
          ::= { baculaMediaTable 1 }
  
          BaculaMediaEntry             ::= SEQUENCE {
            baculaMediaIndex           CounterIndex,

            baculaMediaName            DisplayString,
            baculaMediaSlot            Integer32,
            baculaMediaPool            Integer32,
            baculaMediaType            DisplayString,
            baculaMediaWrittenFirst    DisplayString,
            baculaMediaWrittenLast     DisplayString,
            baculaMediaLabelDate       DisplayString,
            baculaMediaJobs            Integer32,
            baculaMediaFiles           Integer32,
            baculaMediaBlocks          Integer32,
            baculaMediaMounts          Integer32,
            baculaMediaBytes           Integer32,
            baculaMediaErrors          Integer32,
            baculaMediaWrites          Integer32,
            baculaMediaCapacity        Integer32,
            baculaMediaStatus          VolumeStatus,
            baculaMediaRecycle         TrueFalse,
            baculaMediaRetention       Integer32,
            baculaMediaDuration        Integer32,
            baculaMediaMaxJobs         Integer32,
            baculaMediaMaxFiles        Integer32,
            baculaMediaMaxBytes        Integer32,
            baculaMediaInChanger       TrueFalse,
            baculaMediaMediaAddressing TrueFalse,
            baculaMediaReadTime        Integer32,
            baculaMediaWriteTime       Integer32,
            baculaMediaEndFile         Integer32,
            baculaMediaEndBlock        Integer32
          }
  
          baculaMediaIndex             OBJECT-TYPE
            SYNTAX                     CounterIndex
            MAX-ACCESS                 not-accessible
            STATUS                     current
            DESCRIPTION                "Reference Index for each counter."
            ::= { baculaMediaEntry 1 }
  
          baculaMediaName              OBJECT-TYPE
            SYNTAX                     DisplayString
            MAX-ACCESS                 read-only
            STATUS                     current
            DESCRIPTION                "Name of Bacula pool."
            ::= { baculaMediaEntry 2 }

          baculaMediaSlot              OBJECT-TYPE
            SYNTAX                     Integer32
            MAX-ACCESS                 read-only
            STATUS                     current
            DESCRIPTION                "."
            ::= { baculaMediaEntry 3 }

          baculaMediaPool              OBJECT-TYPE
            SYNTAX                     Integer32
            MAX-ACCESS                 read-only
            STATUS                     current
            DESCRIPTION                "."
            ::= { baculaMediaEntry 4 }

          baculaMediaType              OBJECT-TYPE
            SYNTAX                     DisplayString
            MAX-ACCESS                 read-only
            STATUS                     current
            DESCRIPTION                "."
            ::= { baculaMediaEntry 5 }

          baculaMediaWrittenFirst      OBJECT-TYPE
            SYNTAX                     DisplayString
            MAX-ACCESS                 read-only
            STATUS                     current
            DESCRIPTION                "."
            ::= { baculaMediaEntry 6 }

          baculaMediaWrittenLast       OBJECT-TYPE
            SYNTAX                     DisplayString
            MAX-ACCESS                 read-only
            STATUS                     current
            DESCRIPTION                "."
            ::= { baculaMediaEntry 7 }

          baculaMediaLabelDate         OBJECT-TYPE
            SYNTAX                     DisplayString
            MAX-ACCESS                 read-only
            STATUS                     current
            DESCRIPTION                "."
            ::= { baculaMediaEntry 8 }

          baculaMediaJobs              OBJECT-TYPE
            SYNTAX                     Integer32
            MAX-ACCESS                 read-only
            STATUS                     current
            DESCRIPTION                "."
            ::= { baculaMediaEntry 9 }

          baculaMediaFiles             OBJECT-TYPE
            SYNTAX                     Integer32
            MAX-ACCESS                 read-only
            STATUS                     current
            DESCRIPTION                "."
            ::= { baculaMediaEntry 10 }

          baculaMediaBlocks            OBJECT-TYPE
            SYNTAX                     Integer32
            MAX-ACCESS                 read-only
            STATUS                     current
            DESCRIPTION                "."
            ::= { baculaMediaEntry 11 }

          baculaMediaMounts            OBJECT-TYPE
            SYNTAX                     Integer32
            MAX-ACCESS                 read-only
            STATUS                     current
            DESCRIPTION                "."
            ::= { baculaMediaEntry 12 }

          baculaMediaBytes             OBJECT-TYPE
            SYNTAX                     Integer32
            MAX-ACCESS                 read-only
            STATUS                     current
            DESCRIPTION                "."
            ::= { baculaMediaEntry 13 }

          baculaMediaErrors             OBJECT-TYPE
            SYNTAX                     Integer32
            MAX-ACCESS                 read-only
            STATUS                     current
            DESCRIPTION                "."
            ::= { baculaMediaEntry 14 }

          baculaMediaWrites            OBJECT-TYPE
            SYNTAX                     Integer32
            MAX-ACCESS                 read-only
            STATUS                     current
            DESCRIPTION                "."
            ::= { baculaMediaEntry 15 }

          baculaMediaCapacity          OBJECT-TYPE
            SYNTAX                     Integer32
            MAX-ACCESS                 read-only
            STATUS                     current
            DESCRIPTION                "."
            ::= { baculaMediaEntry 16 }

          baculaMediaStatus            OBJECT-TYPE
            SYNTAX                     VolumeStatus
            MAX-ACCESS                 read-only
            STATUS                     current
            DESCRIPTION                "."
            ::= { baculaMediaEntry 17 }

          baculaMediaRecycle           OBJECT-TYPE
            SYNTAX                     TrueFalse
            MAX-ACCESS                 read-only
            STATUS                     current
            DESCRIPTION                "."
            ::= { baculaMediaEntry 18 }

          baculaMediaRetention         OBJECT-TYPE
            SYNTAX                     Integer32
            MAX-ACCESS                 read-only
            STATUS                     current
            DESCRIPTION                "."
            ::= { baculaMediaEntry 19 }

          baculaMediaDuration          OBJECT-TYPE
            SYNTAX                     Integer32
            MAX-ACCESS                 read-only
            STATUS                     current
            DESCRIPTION                "."
            ::= { baculaMediaEntry 20 }

          baculaMediaMaxJobs           OBJECT-TYPE
            SYNTAX                     Integer32
            MAX-ACCESS                 read-only
            STATUS                     current
            DESCRIPTION                "."
            ::= { baculaMediaEntry 21 }

          baculaMediaMaxFiles          OBJECT-TYPE
            SYNTAX                     Integer32
            MAX-ACCESS                 read-only
            STATUS                     current
            DESCRIPTION                "."
            ::= { baculaMediaEntry 22 }

          baculaMediaMaxBytes          OBJECT-TYPE
            SYNTAX                     Integer32
            MAX-ACCESS                 read-only
            STATUS                     current
            DESCRIPTION                "."
            ::= { baculaMediaEntry 23 }

          baculaMediaInChanger         OBJECT-TYPE
            SYNTAX                     TrueFalse
            MAX-ACCESS                 read-only
            STATUS                     current
            DESCRIPTION                "."
            ::= { baculaMediaEntry 24 }

          baculaMediaMediaAddressing   OBJECT-TYPE
            SYNTAX                     TrueFalse
            MAX-ACCESS                 read-only
            STATUS                     current
            DESCRIPTION                "."
            ::= { baculaMediaEntry 25 }

          baculaMediaReadTime          OBJECT-TYPE
            SYNTAX                     Integer32
            MAX-ACCESS                 read-only
            STATUS                     current
            DESCRIPTION                "."
            ::= { baculaMediaEntry 26 }

          baculaMediaWriteTime         OBJECT-TYPE
            SYNTAX                     Integer32
            MAX-ACCESS                 read-only
            STATUS                     current
            DESCRIPTION                "."
            ::= { baculaMediaEntry 27 }

          baculaMediaEndFile           OBJECT-TYPE
            SYNTAX                     Integer32
            MAX-ACCESS                 read-only
            STATUS                     current
            DESCRIPTION                "."
            ::= { baculaMediaEntry 28 }

          baculaMediaEndBlock          OBJECT-TYPE
            SYNTAX                     Integer32
            MAX-ACCESS                 read-only
            STATUS                     current
            DESCRIPTION                "."
            ::= { baculaMediaEntry 29 }
-- }}}
-- }}}

    -- {{{ .1.3.6.1.4.1.8767.2.4 systemStats
    systemStats                        OBJECT IDENTIFIER ::= { snmp 4 }
      -- {{{ .1.3.6.1.4.1.8767.2.4.1   systemUptime
      systemUptime                     OBJECT-TYPE
        SYNTAX                         Integer32
        MAX-ACCESS                     read-only
        STATUS                         current
        DESCRIPTION                    "System uptime (in seconds)."
        ::= { systemStats 1 }
-- }}}

      -- {{{ .1.3.6.1.4.1.8767.2.4.2   systemMemoryTable
      systemMemoryTable                OBJECT-TYPE
        SYNTAX                         SEQUENCE OF SystemMemoryTableEntry
        MAX-ACCESS                     not-accessible
        STATUS                         current
        DESCRIPTION                    "A list of system memory statistic counters"
        ::= { systemStats 2 }
  
        systemMemoryEntry              OBJECT-TYPE
          SYNTAX                       SystemMemoryTableEntry
          MAX-ACCESS                   not-accessible
          STATUS                       current
          DESCRIPTION                  "An entry containing system memory statistics"
          INDEX                        { systemMemoryIndex }
          ::= { systemMemoryTable 1 }
  
          SystemMemoryTableEntry       ::= SEQUENCE {
            systemMemoryIndex          CounterIndex,

            systemMemoryTotal          Integer32,
            systemMemoryUsed           Integer32,
            systemMemoryBuffered       Integer32,
            systemMemoryCached         Integer32,
            systemMemorySwapTotal      Integer32,
            systemMemorySwapUsed       Integer32
          }
  
          systemMemoryIndex            OBJECT-TYPE
            SYNTAX                     CounterIndex
            MAX-ACCESS                 not-accessible
            STATUS                     current
            DESCRIPTION                "Reference Index for each counter."
            ::= { systemMemoryEntry 1 }

          systemMemoryTotal            OBJECT-TYPE
            SYNTAX                     Integer32
            MAX-ACCESS                 read-only
            STATUS                     current
            DESCRIPTION                "Total physical memory in the system."
            ::= { systemMemoryEntry 2 }

          systemMemoryUsed             OBJECT-TYPE
            SYNTAX                     Integer32
            MAX-ACCESS                 read-only
            STATUS                     current
            DESCRIPTION                "Physical memory in use by the system."
            ::= { systemMemoryEntry 3 }

          systemMemoryBuffered         OBJECT-TYPE
            SYNTAX                     Integer32
            MAX-ACCESS                 read-only
            STATUS                     current
            DESCRIPTION                "Memory buffered in the system."
            ::= { systemMemoryEntry 4 }

          systemMemoryCached           OBJECT-TYPE
            SYNTAX                     Integer32
            MAX-ACCESS                 read-only
            STATUS                     current
            DESCRIPTION                "Memory cached in the system."
            ::= { systemMemoryEntry 5 }

          systemMemorySwapTotal        OBJECT-TYPE
            SYNTAX                     Integer32
            MAX-ACCESS                 read-only
            STATUS                     current
            DESCRIPTION                "Total amount of swap space in the system."
            ::= { systemMemoryEntry 6 }

          systemMemorySwapUsed         OBJECT-TYPE
            SYNTAX                     Integer32
            MAX-ACCESS                 read-only
            STATUS                     current
            DESCRIPTION                "Swap memory in use by the system."
            ::= { systemMemoryEntry 7 }
-- }}}

      -- {{{ .1.3.6.1.4.1.8767.2.4.3   systemCPUTable
      systemCPUTable                   OBJECT-TYPE
        SYNTAX                         SEQUENCE OF SystemCPUTableEntry
        MAX-ACCESS                     not-accessible
        STATUS                         current
        DESCRIPTION                    "A list of system CPU statistic counters"
        ::= { systemStats 3 }
  
        systemCPUEntry                 OBJECT-TYPE
          SYNTAX                       SystemCPUTableEntry
          MAX-ACCESS                   not-accessible
          STATUS                       current
          DESCRIPTION                  "An entry containing system CPU statistics"
          INDEX                        { systemCPUIndex }
          ::= { systemCPUTable 1 }
  
          SystemCPUTableEntry          ::= SEQUENCE {
            systemCPUIndex             CounterIndex,

            systemCPUTasksTotal        Integer32,
            systemCPUTasksRunning      Integer32,
            systemCPUTasksSleeping     Integer32,
            systemCPUTasksStopped      Integer32,
            systemCPUTasksZombies      Integer32,

            systemCPUUsageUser         Integer32,
            systemCPUUsageSystem       Integer32,
            systemCPUUsageNice         Integer32,
            systemCPUUsageIdle         Integer32,
            systemCPUUsageIOWait       Integer32
          }
  
          systemCPUIndex               OBJECT-TYPE
            SYNTAX                     CounterIndex
            MAX-ACCESS                 not-accessible
            STATUS                     current
            DESCRIPTION                "Reference Index for each counter."
            ::= { systemCPUEntry 1 }

          systemCPUTasksTotal          OBJECT-TYPE
            SYNTAX                     Integer32
            MAX-ACCESS                 read-only
            STATUS                     current
            DESCRIPTION                "."
            ::= { systemCPUEntry 2 }

          systemCPUTasksRunning        OBJECT-TYPE
            SYNTAX                     Integer32
            MAX-ACCESS                 read-only
            STATUS                     current
            DESCRIPTION                "."
            ::= { systemCPUEntry 3 }

          systemCPUTasksSleeping       OBJECT-TYPE
            SYNTAX                     Integer32
            MAX-ACCESS                 read-only
            STATUS                     current
            DESCRIPTION                "."
            ::= { systemCPUEntry 4 }

          systemCPUTasksStopped        OBJECT-TYPE
            SYNTAX                     Integer32
            MAX-ACCESS                 read-only
            STATUS                     current
            DESCRIPTION                "."
            ::= { systemCPUEntry 5 }

          systemCPUTasksZombies        OBJECT-TYPE
            SYNTAX                     Integer32
            MAX-ACCESS                 read-only
            STATUS                     current
            DESCRIPTION                "."
            ::= { systemCPUEntry 6 }

          systemCPUUsageUser           OBJECT-TYPE
            SYNTAX                     Integer32
            MAX-ACCESS                 read-only
            STATUS                     current
            DESCRIPTION                "."
            ::= { systemCPUEntry 7 }

          systemCPUUsageSystem         OBJECT-TYPE
            SYNTAX                     Integer32
            MAX-ACCESS                 read-only
            STATUS                     current
            DESCRIPTION                "."
            ::= { systemCPUEntry 8 }

          systemCPUUsageNice           OBJECT-TYPE
            SYNTAX                     Integer32
            MAX-ACCESS                 read-only
            STATUS                     current
            DESCRIPTION                "."
            ::= { systemCPUEntry 9 }

          systemCPUUsageIdle           OBJECT-TYPE
            SYNTAX                     Integer32
            MAX-ACCESS                 read-only
            STATUS                     current
            DESCRIPTION                "."
            ::= { systemCPUEntry 10 }

          systemCPUUsageIOWait         OBJECT-TYPE
            SYNTAX                     Integer32
            MAX-ACCESS                 read-only
            STATUS                     current
            DESCRIPTION                "."
            ::= { systemCPUEntry 11 }
-- }}}

      -- {{{ .1.3.6.1.4.1.8767.2.4.4   systemLoadTable
      systemLoadTable                  OBJECT-TYPE
        SYNTAX                         SEQUENCE OF SystemLoadTableEntry
        MAX-ACCESS                     not-accessible
        STATUS                         current
        DESCRIPTION                    "A list of system load average statistic counters"
        ::= { systemStats 4 }
  
        systemLoadEntry                OBJECT-TYPE
          SYNTAX                       SystemLoadTableEntry
          MAX-ACCESS                   not-accessible
          STATUS                       current
          DESCRIPTION                  "An entry containing system load average statistics"
          INDEX                        { systemLoadIndex }
          ::= { systemLoadTable 1 }
  
          SystemLoadTableEntry         ::= SEQUENCE {
            systemLoadIndex            CounterIndex,

            systemLoadLastOne          Integer32,
            systemLoadLastFive         Integer32,
            systemLoadLastFifteen      Integer32
          }
  
          systemLoadIndex              OBJECT-TYPE
            SYNTAX                     CounterIndex
            MAX-ACCESS                 not-accessible
            STATUS                     current
            DESCRIPTION                "Reference Index for each counter."
            ::= { systemLoadEntry 1 }

          systemLoadLastOne            OBJECT-TYPE
            SYNTAX                     Integer32
            MAX-ACCESS                 read-only
            STATUS                     current
            DESCRIPTION                "."
            ::= { systemLoadEntry 2 }

          systemLoadLastFive           OBJECT-TYPE
            SYNTAX                     Integer32
            MAX-ACCESS                 read-only
            STATUS                     current
            DESCRIPTION                "."
            ::= { systemLoadEntry 3 }

          systemLoadLastFifteen        OBJECT-TYPE
            SYNTAX                     Integer32
            MAX-ACCESS                 read-only
            STATUS                     current
            DESCRIPTION                "."
            ::= { systemLoadEntry 4 }

-- }}}
-- }}}

    -- {{{ .1.3.6.1.4.1.8767.2.5 packageStats
    packageStats                       OBJECT IDENTIFIER ::= { snmp 5 }
      -- {{{ .1.3.6.1.4.1.8767.2.5.1 packageStatsTable
      packageStatsTable                    OBJECT-TYPE
        SYNTAX                             SEQUENCE OF PackageStatsEntry
        MAX-ACCESS                         not-accessible
        STATUS                             current
        DESCRIPTION                        "A list of package statistic information."
        ::= { packageStats 1 }

        packageStatsEntry                  OBJECT-TYPE
          SYNTAX                           PackageStatsEntry
          MAX-ACCESS                       not-accessible
          STATUS                           current
          DESCRIPTION                      "Package statistics table"
          INDEX                            { packageIndexStats }
          ::= { packageStatsTable 1 }

          PackageStatsEntry                ::= SEQUENCE {
            packageIndexStats              CounterIndex,

            packageName                    DisplayString,
            packageVersion                 DisplayString,
            packageDesc                    DisplayString,
            packageStatus                  DisplayString
          }

          packageIndexStats                OBJECT-TYPE
            SYNTAX                         CounterIndex
            MAX-ACCESS                     not-accessible
            STATUS                         current
            DESCRIPTION                    "Reference Index for each counter."
            ::= { packageStatsEntry 1 }

          packageName                      OBJECT-TYPE
            SYNTAX                         DisplayString
            MAX-ACCESS                     read-only
            STATUS                         current
            DESCRIPTION                    "Name of package"
            ::= { packageStatsEntry 2 }

          packageVersion                   OBJECT-TYPE
            SYNTAX                         DisplayString
            MAX-ACCESS                     read-only
            STATUS                         current
            DESCRIPTION                    "xx"
            ::= { packageStatsEntry 3 }

          packageDesc                      OBJECT-TYPE
            SYNTAX                         DisplayString
            MAX-ACCESS                     read-only
            STATUS                         current
            DESCRIPTION                    "xx"
            ::= { packageStatsEntry 4 }

          packageStatus                    OBJECT-TYPE
            SYNTAX                         DisplayString
            MAX-ACCESS                     read-only
            STATUS                         current
            DESCRIPTION                    "xx"
            ::= { packageStatsEntry 5 }
-- }}}

      -- {{{ .1.3.6.1.4.1.8767.2.5.2 packageInfoTable
      packageInfoTable                     OBJECT-TYPE
        SYNTAX                             SEQUENCE OF PackageInfoEntry
        MAX-ACCESS                         not-accessible
        STATUS                             current
        DESCRIPTION                        "Package statistics table"
        ::= { packageStats 2 }

        packageInfoEntry                   OBJECT-TYPE
          SYNTAX                           PackageInfoEntry
          MAX-ACCESS                       not-accessible
          STATUS                           current
          DESCRIPTION                      "Package statistics table"
          INDEX                            { packageIndexInfo }
          ::= { packageInfoTable 1 }

          PackageInfoEntry                ::= SEQUENCE {
            packageIndexInfo              CounterIndex,

            packagePriority               DisplayString,
            packageSection                DisplayString,
            packageMaintainer             DisplayString,
            packageSource                 DisplayString,
            packageDepends                DisplayString,
            packageRecommends             DisplayString,
            packageSuggests               DisplayString,
            packageSize                   DisplayString,
            packageMD5Sum                 DisplayString
          }

          packageIndexInfo                 OBJECT-TYPE
            SYNTAX                         CounterIndex
            MAX-ACCESS                     not-accessible
            STATUS                         current
            DESCRIPTION                    "Reference Index for each counter."
            ::= { packageInfoEntry  1 }

          packagePriority                  OBJECT-TYPE
            SYNTAX                         DisplayString
            MAX-ACCESS                     read-only
            STATUS                         current
            DESCRIPTION                    "xx"
            ::= { packageInfoEntry  2 }

          packageSection                   OBJECT-TYPE
            SYNTAX                         DisplayString
            MAX-ACCESS                     read-only
            STATUS                         current
            DESCRIPTION                    "xx"
            ::= { packageInfoEntry  3 }

          packageMaintainer                OBJECT-TYPE
            SYNTAX                         DisplayString
            MAX-ACCESS                     read-only
            STATUS                         current
            DESCRIPTION                    "xx"
            ::= { packageInfoEntry  4 }

          packageSource                    OBJECT-TYPE
            SYNTAX                         DisplayString
            MAX-ACCESS                     read-only
            STATUS                         current
            DESCRIPTION                    "xx"
            ::= { packageInfoEntry  5 }

          packageDepends                   OBJECT-TYPE
            SYNTAX                         DisplayString
            MAX-ACCESS                     read-only
            STATUS                         current
            DESCRIPTION                    "xx"
            ::= { packageInfoEntry  6 }

          packageRecommends                OBJECT-TYPE
            SYNTAX                         DisplayString
            MAX-ACCESS                     read-only
            STATUS                         current
            DESCRIPTION                    "xx"
            ::= { packageInfoEntry  7 }

          packageSuggests                  OBJECT-TYPE
            SYNTAX                         DisplayString
            MAX-ACCESS                     read-only
            STATUS                         current
            DESCRIPTION                    "xx"
            ::= { packageInfoEntry  8 }

          packageSize                      OBJECT-TYPE
            SYNTAX                         DisplayString
            MAX-ACCESS                     read-only
            STATUS                         current
            DESCRIPTION                    "xx"
            ::= { packageInfoEntry  9 }

          packageMD5Sum                    OBJECT-TYPE
            SYNTAX                         DisplayString
            MAX-ACCESS                     read-only
            STATUS                         current
            DESCRIPTION                    "xx"
            ::= { packageInfoEntry 10 }
-- }}}
-- }}}
END

-- Local variables:
-- mode: text
-- mode: folding
-- mode: font-lock
-- indent-tabs-mode: nil
